# -*- coding: utf-8 -*-
"""Thin entry point FreeCAD runs on launch -- AND re-runs to update a live hub.

All the real logic is in freecad_viewer.py (same folder) so it stays shared across every
project. This macro reads the launcher's environment -- FREECAD_VIEW_STEP (the initial
project to open as a tab) and FREECAD_VIEW_INBOX (a directory later launches drop more
projects into) -- and starts the hub. Project-agnostic: the same macro serves every repo.

⚠ RUNNING THIS MACRO A SECOND TIME IS THE CODE-UPDATE PATH, AND THE REVIVE PATH.
    freecad.exe --single-instance <this file>
executes it INSIDE the already-running FreeCAD (measured: process count stays at 1 and the
codestamp is rewritten). FreeCAD reads the macro from disk each time, so macro edits land by
themselves; the viewer module does NOT, because `import` returns the copy already in memory
-- so this macro reloads it explicitly below.

That one command therefore covers all three things the launcher used to need a process id
and a taskkill for:

    new viewer code into a live hub   reload, below
    a wedged watch loop               shutdown() + reload rebuilds the QTimer
    a hub that is simply missing      nothing running to forward to, so launch normally

It is affordable only because a tab now carries its own provenance (freecad_viewer's
_stamp_doc): reloading re-imports no geometry and costs no tab, no camera and no hidden
part. Before that, updating the code meant restarting FreeCAD.
"""

import os
import sys
import importlib
import tempfile

# Locate this macro's folder so we can import the shared viewer module next to it.
# Normally __file__ is defined (FreeCAD runs the macro from its path); if it isn't, the
# launcher (freecad_view.py) passes the dir via the environment, so we never hardcode an
# install location.
try:
    _HERE = os.path.dirname(os.path.realpath(__file__))
except NameError:
    _HERE = os.environ.get("FREECAD_VIEW_MACRO_DIR", "").strip()
if _HERE not in sys.path:
    sys.path.insert(0, _HERE)

import FreeCAD as App

# The launcher normally passes both of these in the environment. It cannot always: a macro
# forwarded by --single-instance runs inside the ALREADY-RUNNING FreeCAD, with THAT
# process's environment -- and if the user started FreeCAD themselves, there is no
# FREECAD_VIEW_* in it at all. So the inbox falls back to the same well-known temp path
# freecad_view._INBOX derives, which is how a build still gets its tab when the hub has to
# be planted in a FreeCAD nobody launched for it. An empty step is normal on a re-run: the
# projects are already open and carry their own provenance.
_DEFAULT_INBOX = os.path.join(tempfile.gettempdir(), "freecad_viewer_inbox")
_step = os.environ.get("FREECAD_VIEW_STEP", "").strip()
_inbox = os.environ.get("FREECAD_VIEW_INBOX", "").strip() or _DEFAULT_INBOX
_HB = os.path.join(tempfile.gettempdir(), "freecad_viewer_hub.heartbeat")


def _other_freecads():
    """How many FreeCAD processes exist besides this one. None when it cannot be told."""
    try:
        import subprocess
        if os.name == "nt":
            out = subprocess.run(
                ["tasklist", "/FI", "IMAGENAME eq freecad.exe", "/NH", "/FO", "CSV"],
                capture_output=True, text=True, timeout=10,
                creationflags=0x08000000).stdout.lower()          # CREATE_NO_WINDOW
            return max(0, out.count("freecad.exe") - 1)
        r = subprocess.run(["pgrep", "-f", "[Ff]reeCAD"],
                           capture_output=True, text=True, timeout=10)
        return max(0, len([ln for ln in r.stdout.split() if ln.strip()]) - 1)
    except Exception:
        return None


def _is_failed_handoff():
    """True if this macro is running in a FreeCAD that should never have opened.

    ⚠ THIS IS WHY A SECOND FreeCAD WINDOW APPEARED (user, 2026-10-04). The launcher
    refreshes a live hub with `freecad.exe --single-instance <this macro>`. That call only
    FORWARDS to the running FreeCAD if it answers its local socket inside FreeCAD's own
    short connect timeout. A hub whose main thread is inside a STEP import -- or is wedged,
    which is exactly when a refresh is asked for -- does not answer, and FreeCAD's fallback
    is to carry on starting as a NORMAL NEW INSTANCE and run the macro there. So the
    "non-destructive refresh" silently became a second hub: same heartbeat, same inbox,
    two windows racing for every tab.

    The launcher cannot see which of the two happened; this process can. FREECAD_VIEW_REFRESH
    is set only in the environment of the process the refresh spawned -- a forwarded macro
    runs in the OLD process, whose environment does not have it. So: the variable is set,
    no viewer is loaded here yet, and another FreeCAD exists => the hand-off failed and
    this process is the duplicate. It must close, not become a hub.

    "Cannot tell" counts as a duplicate: a refresh is only ever attempted when the launcher
    saw a FreeCAD running, and if that one has since exited the next build launches a hub
    the normal way."""
    if not os.environ.get("FREECAD_VIEW_REFRESH", "").strip():
        return False
    if "freecad_viewer" in sys.modules:
        return False                    # a hub born from a refresh, being refreshed again
    others = _other_freecads()
    return others is None or others > 0


def _close_duplicate():
    """Close this FreeCAD without opening anything, and leave a note the launcher prints."""
    import time
    try:
        with open(_HB + ".duplicate", "w", encoding="utf-8") as f:
            f.write("%r refresh did not reach the running FreeCAD (it was busy or "
                    "unresponsive); the extra FreeCAD closed itself instead of becoming "
                    "a second window\n" % time.time())
    except OSError:
        pass
    App.Console.PrintWarning("[viewer] another FreeCAD is the hub; closing this one\n")
    try:
        import FreeCADGui as Gui
        from PySide import QtCore
        QtCore.QTimer.singleShot(0, Gui.getMainWindow().close)
        QtCore.QTimer.singleShot(5000, lambda: os._exit(0))   # nothing here to lose
    except Exception:
        os._exit(0)


def _compiles(path):
    """True if `path` is syntactically valid Python.

    ⚠ CHECKED BEFORE reload(), NOT AFTER. importlib.reload re-executes the module in
    place, so a file with a syntax error leaves `freecad_viewer` half-defined -- and we
    would already have called shutdown() on the working copy, i.e. a broken hub with its
    timer stopped. Compiling first means a typo costs nothing: the old code keeps running
    and the error is reported."""
    try:
        with open(path, "rb") as f:
            compile(f.read(), path, "exec")
        return True
    except Exception as e:
        App.Console.PrintError("[viewer] %s will not compile, keeping the running copy: %s\n"
                               % (os.path.basename(path), e))
        return False


def _viewer():
    """The viewer module, reloaded from disk if this is a re-run."""
    mod = sys.modules.get("freecad_viewer")
    if mod is None:
        import freecad_viewer as mod           # first run in this process
        return mod
    if not _compiles(os.path.join(_HERE, "freecad_viewer.py")):
        return mod
    try:
        mod.shutdown()                          # drop the old QTimer + shortcuts first
    except Exception as e:
        App.Console.PrintError("[viewer] shutdown before reload failed: %s\n" % e)
    try:
        mod = importlib.reload(mod)
        App.Console.PrintMessage("[viewer] reloaded viewer code in place\n")
    except Exception as e:
        # It compiled but blew up while executing. The old copy is already detached and
        # cannot be recovered, so say so loudly -- the launcher will see a stale heartbeat
        # and re-run this macro, which retries the reload against whatever is on disk then.
        App.Console.PrintError("[viewer] reload FAILED, hub is down until the next run: %s\n" % e)
        raise
    return mod


# ⚠ A MACRO FAILURE IS OTHERWISE INVISIBLE FROM OUTSIDE. FreeCAD sends the traceback to its
# Report view, which no build can read -- and the launcher now DEPENDS on this macro running
# (it is the code-update and revive path), so "nothing happened and nobody said why" is the
# one outcome that must not be possible. Write it beside the heartbeat instead; the file is
# removed on success, so its presence always means the last run failed.
_ERR = os.path.join(tempfile.gettempdir(), "freecad_viewer_hub.heartbeat") + ".error"
if _is_failed_handoff():
    _close_duplicate()
else:
    try:
        _viewer().start_hub(inbox_dir=_inbox, initial_step=_step or None)
    except Exception:
        import traceback
        try:
            with open(_ERR, "w", encoding="utf-8") as _f:
                _f.write(traceback.format_exc())
        except OSError:
            pass
        raise
    else:
        try:
            os.remove(_ERR)
        except OSError:
            pass
